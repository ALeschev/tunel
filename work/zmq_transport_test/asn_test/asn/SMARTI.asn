-- SMARTI - Smart Telephone Integration
SMARTI

DEFINITIONS IMPLICIT TAGS ::=
BEGIN

-- Top level message
SmarTIMessage ::= SEQUENCE
{
  version [0] INTEGER,
  legID   [1] LegId,
  body    [2] SmarTIBody
}

SmarTIBody ::= CHOICE
{
  connectionRequest        [1] ConnectionRequestType,
  connectionResponse       [2] ConnectionResponseType,
  connectionReject         [3] ConnectionRejectType,
  connectionUpdateRequest  [4] ConnectionUpdateRequestType,
  connectionUpdateResponse [5] ConnectionUpdateResponseType,
  seize                    [6] SeizeType,
  progress                 [7] ProgressType,
  answer                   [8] AnswerType,
  release                  [9] ReleaseType
}

ConnectionRequestType ::= SEQUENCE
{
  updateTimeout [1] INTEGER OPTIONAL
}

ConnectionResponseType ::= SEQUENCE
{
  updateTimeout [1] INTEGER OPTIONAL
}

ConnectionRejectType ::= SEQUENCE
{
  cause      [1] INTEGER,
  diagnostic [2] OCTET STRING OPTIONAL
}

ConnectionUpdateRequestType ::= SEQUENCE
{
  timestamp [1] Timestamp OPTIONAL,
  other     [2] AdditionalInformation OPTIONAL
}

ConnectionUpdateResponseType ::= SEQUENCE
{
  timestamp [1] Timestamp OPTIONAL,
  other     [2] AdditionalInformation OPTIONAL
}

SeizeType ::= SEQUENCE
{
  vatsId                  [0] OCTET STRING,
  cdpn                    [2] CalledPartyNumber,
  cgpn                    [3] CallingPartyNumber  OPTIONAL,
  callRef                 [1] CallReference OPTIONAL,
  category                [4] CallingPartysCategory OPTIONAL,
  tgId                    [5] TrunkGroupId OPTIONAL,
  originalCDPN            [6] OriginalCalledNumber OPTIONAL,
  genericNumber           [7] GenericNumber         OPTIONAL,
  redirectingNumber       [8] RedirectingNumber     OPTIONAL,
  redirectionInformation  [9] RedirectionInformation OPTIONAL,
  fci                    [10] ForwardCallIndicators  OPTIONAL,
  usi                    [11] UserServiceInformation OPTIONAL,
  uti                    [12] UserTeleserviceInformation OPTIONAL,
  tmr                    [13] TransmissionMediumRequirement OPTIONAL,
  timestamp              [14] Timestamp,
  applicationId          [15] ApplicationID,
  noCDR                  [16] BOOLEAN OPTIONAL,
  bridge                 [17] Bridge OPTIONAL,
  detached               [18] BOOLEAN OPTIONAL,
  toLog                  [19] OCTET STRING OPTIONAL,
  other                  [20] AdditionalInformation OPTIONAL
}  

ProgressType ::= SEQUENCE 
{
  event               [0] EventInformation,
  cause               [1] Cause OPTIONAL,
  obci                [2] OptionalBackwardCallInidicators OPTIONAL,
  gnotification       [3] GenericNotificationIndicatorList OPTIONAL,
  redirectionNumber   [4] RedirectionNumber OPTIONAL,
  redirectionRestInd  [5] RedirectionNumberRestriction OPTIONAL,
  callDiversion       [6] CallDiversionInformation OPTIONAL,
  callTransferNumber  [7] CallTransferNumber OPTIONAL,
  timestamp           [8] Timestamp,
  collectedInfo       [9] CollectedInfo OPTIONAL, --detected digits, tones
  play               [10] PlayInfo OPTIONAL,
  noCDR              [11] BOOLEAN OPTIONAL,
  bridge             [12] Bridge OPTIONAL,
  detached           [13] BOOLEAN OPTIONAL,
  toLog              [14] OCTET STRING OPTIONAL,
  other              [15] AdditionalInformation OPTIONAL
}

AnswerType ::= SEQUENCE 
{
  bci                 [0] BackwardCallIndicators OPTIONAL,
  obci                [1] OptionalBackwardCallInidicators OPTIONAL,
  gnotification       [2] GenericNotificationIndicatorList OPTIONAL,
  connectedNumber     [3] ConnectedNumber OPTIONAL,
  genericNumber       [4] GenericNumber OPTIONAL,
  redirectionNumber   [5] RedirectionNumber OPTIONAL,
  redirectionRestInd  [6] RedirectionNumberRestriction OPTIONAL,
  timestamp           [7] Timestamp,
  play                [8] PlayInfo OPTIONAL,
  detect              [9] Detect OPTIONAL,
  noCDR              [10] BOOLEAN OPTIONAL,
  bridge             [11] Bridge OPTIONAL,
  detached           [12] BOOLEAN OPTIONAL,
  toLog              [13] OCTET STRING OPTIONAL,
  other              [14] AdditionalInformation OPTIONAL
}

ReleaseType ::= SEQUENCE 
{
  cause     [0] Cause,
  timestamp [1] Timestamp,
  noCDR     [2] BOOLEAN OPTIONAL,
  detached  [3] BOOLEAN OPTIONAL,
  toLog     [4] OCTET STRING OPTIONAL,
  other     [5] AdditionalInformation OPTIONAL
}

CallReference ::= OCTET STRING (SIZE(1..maxCallReferenceLength))
CalledPartyNumber ::= SEQUENCE
{
  nai     [0] NatureOfAddressInd,
  npi     [1] NumberingPlanInd,
  inn     [2] InternalNetworkNumberInd,
  address [3] OCTET STRING
}

CallingPartyNumber ::= SEQUENCE
{ 
  nai       [0] NatureOfAddressInd,
  screening [1] ScreeningInd,
  apri      [2] AddressPresentationRestrictionInd,
  npi       [3] NumberingPlanInd,
  ni        [4] NumberIncompleteInd,
  address   [5] OCTET STRING
}

CallingPartysCategory ::= OCTET STRING (SIZE(1))
TrunkGroupId ::= INTEGER

OriginalCalledNumber ::= SEQUENCE
{
  nai     [0] NatureOfAddressInd,
  apri    [1] AddressPresentationRestrictionInd,
  npi     [2] NumberingPlanInd,
  address [3] OCTET STRING
}

GenericNumber ::= SEQUENCE
{
  nqi       [0] NumberQualifierInd,
  nai       [1] NatureOfAddressInd,
  screening [2] ScreeningInd,
  apri      [3] AddressPresentationRestrictionInd,
  npi       [4] NumberingPlanInd,
  ni        [5] NumberIncompleteInd,
  address   [6] OCTET STRING
}

RedirectingNumber ::= SEQUENCE
{
  nai     [0] NatureOfAddressInd,
  apri    [1] AddressPresentationRestrictionInd,
  npi     [2] NumberingPlanInd,
  address [3] OCTET STRING
}

RedirectionInformation ::= SEQUENCE
{
  redirecting [0] RedirectingInd,
  oreason     [1] OriginalRedirectionReason,
  counter     [2] RedirectionCounter,
  reason      [3] RedirectingReason
}

ForwardCallIndicators ::= OCTET STRING(SIZE(2))
UserServiceInformation ::= OCTET STRING
UserTeleserviceInformation ::= OCTET STRING
TransmissionMediumRequirement ::= OCTET STRING(SIZE(1))
Timestamp ::= OCTET STRING
ApplicationID ::= OCTET STRING

Bridge ::= SEQUENCE
{
  leg1 [0] LegId,
  leg2 [1] LegId
}

AdditionalInformation ::= SET OF KVElement
KVElement ::= SEQUENCE
{
  key   [0] OCTET STRING,
  value [1] OCTET STRING
}

EventInformation ::= SEQUENCE
{
  event [0] EventIndicator,
  presentation [0] EventPresentationInd
}

Cause ::= OCTET STRING
OptionalBackwardCallInidicators ::= OCTET STRING(SIZE(1))
GenericNotificationIndicatorList ::= SET OF GenericNotificationIndicator
GenericNotificationIndicator ::= ENUMERATED
{
  userSuspended(0),
  userResumed(1),
  bearerServiceChange(2),
  callCompletionDelay(4),
  conferenceEstablished(130),
  conferenceDisconnected(131),
  otherPartyAdded(132),
  isolated(133),
  reattached(134),
  otherPartyIsolated(135),
  otherPartyReattached(136),
  otherPartySplit(137),
  otherPartyDisconnected(138),
  conferenceFloating(139),
  callIsAWaitingCall(192),
  callTransferAlerting(209),
  callTransferActive(210),
  remoteHold(241),
  remoteRetrieval(242),
  callIsDiverting(243)
}

RedirectionNumber ::= SEQUENCE
{
  nai     [0] NatureOfAddressInd,
  npi     [1] NumberingPlanInd,
  inn     [2] InternalNetworkNumberInd,
  address [3] OCTET STRING
}

RedirectionNumberRestriction ::= ENUMERATED
{
  presentationAllowed(0),
  presentationRestricted(1)
}

CallDiversionInformation ::= SEQUENCE
{
  nso [0] NotificationSubscriptionOptions,
  redirectingReason [1] RedirectingReason
}

NotificationSubscriptionOptions ::= ENUMERATED
{
  unknown(0),
  presentationNotAllowed(1),
  presentationAllowedWithRedirectionNumber(2),
  presentationAllowedWithoutRedirectionNumber(3)
}

CallTransferNumber ::= SEQUENCE
{
  nai       [0] NatureOfAddressInd,
  screening [1] ScreeningInd,
  apri      [2] AddressPresentationRestrictionInd,
  npi       [3] NumberingPlanInd,
  address   [4] OCTET STRING
}

CollectedInfo ::= CHOICE
{
  tone   [0] ToneInfo,
  signal [1] SignalInfo
}

ToneInfo ::= ENUMERATED
{
  dtmf0(0),
  dtmf1(1),
  dtmf2(2),
  dtmf3(3),
  dtmf4(4),
  dtmf5(5),
  dtmf6(6),
  dtmf7(7),
  dtmf8(8),
  dtmf9(9),
  dtmfA(10),
  dtmfB(11),
  dtmfC(12),
  dtmfD(13),
  dtmfstar(14),
  dtmfhash(15),
  dialTone(16),
  busy(17),
  ringback(18)
}

SignalInfo ::= OCTET STRING

PlayInfo ::= SET
{
  tone [0] ToneInfo,
  file [1] OCTET STRING -- URL
}

BackwardCallIndicators ::= OCTET STRING(SIZE(2))

ConnectedNumber ::= SEQUENCE
{
  nai       [0] NatureOfAddressInd,
  screening [1] ScreeningInd,
  apri      [2] AddressPresentationRestrictionInd,
  npi       [3] NumberingPlanInd,
  address   [4] OCTET STRING
}

Detect ::= OCTET STRING

--

NatureOfAddressInd ::= OCTET STRING(SIZE(1))
NumberingPlanInd ::= OCTET STRING(SIZE(1))
InternalNetworkNumberInd ::= ENUMERATED
{
  routingAllowed(0),
  routingNotAllowed(1)
}

ScreeningInd ::= ENUMERATED
{
  userProvidedNotVerified(0),
  userProvidedVerifiedAndPassed(1),
  userProvidedVerifiedAndFailed(2),
  networkProvided(3)
}

AddressPresentationRestrictionInd ::= ENUMERATED
{
  presentationAllowed(0),
  presentationRestricted(1),
  addressNotAvailable(2),
  reserved(3)
}

NumberIncompleteInd ::= ENUMERATED
{
  complete(0),
  incomplete(1)
}

NumberQualifierInd ::= OCTET STRING(SIZE(1))

RedirectingInd ::= ENUMERATED
{
  noRedirection(0),
  callRerouted(1),
  callReroutedAllRestricted(2),
  callDiverted(3),
  callDivertedAllRestricted(4),
  callReroutedNumberRestricted(5),
  callDivertedNumberRestricted(6),
  spare(7)
}

OriginalRedirectionReason ::= ENUMERATED
{
  unknownNotAvailable(0),
  userBusy(1),
  noReply(2),
  unconditional(3),
  spare4(4),
  spare5(5),
  spare6(6),
  spare7(7),
  spare8(8),
  spare9(9),
  spare10(10),
  spare11(11),
  spare12(12),
  spare13(13),
  spare14(14),
  spare15(15)
}

RedirectionCounter ::= BIT STRING(SIZE(3))

RedirectingReason ::= ENUMERATED
{
  unknownNotAvailable(0),
  userBusy(1),
  noReply(2),
  unconditional(3),
  deflectionDuringAlerting(4),
  deflectionImmediateResponse(5),
  mobileSubscriberNotReachable(6),
  spare7(7),
  spare8(8),
  spare9(9),
  spare10(10),
  spare11(11),
  spare12(12),
  spare13(13),
  spare14(14),
  spare15(15)  
}

LegId ::= SEQUENCE
{
  swSessionID [1] OCTET STRING,
  appSessionID [2] OCTET STRING
}

EventIndicator ::= BIT STRING(SIZE(7)) -- 7bit value with valid values from EventIndicatorVal
EventIndicatorVal ::= ENUMERATED
{
  alerting(1),
  progress(2),
  inband(3),
  callForwardedOnBusy(4),
  callForwardedOnNoReply(5),
  callForwardedUnconditional(6)
}

EventPresentationInd ::= ENUMERATED
{
  noIndication(0),
  restricted(1)
}

maxCallReferenceLength INTEGER ::= 5
END
